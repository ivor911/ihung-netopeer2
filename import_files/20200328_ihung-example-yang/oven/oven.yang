module oven {
  namespace "urn:sysrepo:oven";
  prefix ov;

  import ietf-inet-types {
    prefix inet;
  }

  import ietf-yang-types {
    prefix yang;
  }

  revision 2018-01-19 {
    description "Initial revision.";
  }
  typedef oven-temperature {
    description "Temperature range that is accepted by the oven.";
    type uint8 {
      range "0..250";
    }
  }

  container oven {
    description "Configuration container of the oven.";
    leaf turned-on {
      description "Main switch determining whether the oven is on or off.";
      type boolean;
      default false;
    }
    leaf temperature {
      description "Slider for configuring the desired temperature.";
      type oven-temperature;
      default 0;
    }

    leaf Interface-Name {
      /*
      type rb-nos-types:interface-name;
      */
      type string {
        length "1..64";
      }
      description
        "Interface name, e.g., eth0, eth1, eth2, lte1";
    }

    leaf Interface-Enable {
      type boolean;
      default "false";
      description
        "Enable(true) or disable(false) this interface";
    }


    leaf Hostname {
      type string {
        length "1..256";
      }
      description
      "NOS hostname.";

      default "rbbn-nos-hostname";
    }

    list Static-IP-Address-List {
      key "IP-Address-Index";
      description
        "Configure the static IP addresses.";
      leaf IP-Address-Index {
        type uint32;
        description
          "IP Address index.";
      }

      leaf IP-Address {
        /*
        type rb-nos-types:ip-address;
        */
        type inet:ip-address;
        mandatory true;
        description
          "IP address.";
      }
      leaf IP-Address-Prefix {
        /*
        type rb-nos-types:ip-prefix;
        */
        type inet:ip-prefix;
        mandatory true;
        description
          "Network subnet mask.";
      }
      leaf Default-Gateway {
        /*
        type rb-nos-types:ip-address;
        */
        type inet:ip-address;
        description
          "Default Gateway (Default Router).";
      }
    }
  }
  container oven-state {
    description "State data container of the oven.";
    config false;
    leaf temperature {
      description "Actual temperature inside the oven.";
      type oven-temperature;
    }
    leaf food-inside {
      description "Informs whether the food is inside the oven or not.";
      type boolean;
    }
  }
  rpc insert-food {
    description "Operation to order the oven to put the prepared food inside.";
    input {
      leaf time {
        description "Parameter determining when to perform the operation.";
        type enumeration {
          enum now {
            description "Put the food in the oven immediately.";
          }
          enum on-oven-ready {
            description
              "Put the food in once the temperature inside
               the oven is at least the configured one. If it
               is already, the behaviour is similar to 'now'.";
          }
        }
      }
    }
  }
  rpc remove-food {
    description "Operation to order the oven to take the food out.";
  }
  notification oven-ready {
    description
      "Event of the configured temperature matching the actual
       temperature inside the oven. If the configured temperature
       is lower than the actual one, no notification is generated
       when the oven cools down to the configured temperature.";
  }
}
